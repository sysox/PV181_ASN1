-- RFC 8017, Appendix A.1.1 and A.1.2: https://www.rfc-editor.org/rfc/rfc8017#appendix-A.1

RSA DEFINITIONS ::= BEGIN
    RSAPublicKey ::= SEQUENCE {
        modulus           INTEGER,  -- n
        publicExponent    INTEGER   -- e
    }

    Version ::= INTEGER
    RSAPrivateKey ::= SEQUENCE {
        version           Version,
        modulus           INTEGER,  -- n
        publicExponent    INTEGER,  -- e
        privateExponent   INTEGER,  -- d
        prime1            INTEGER,  -- p
        prime2            INTEGER,  -- q
        exponent1         INTEGER,  -- d mod (p-1)
        exponent2         INTEGER,  -- d mod (q-1)
        coefficient       INTEGER   -- (inverse of q) mod p
    }
END
